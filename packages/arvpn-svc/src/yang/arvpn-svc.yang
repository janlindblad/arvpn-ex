module arvpn-svc {
  yang-version 1.1;
  namespace "http://example.com/arvpn-svc";
  prefix arvpn-svc;

  import ietf-inet-types {
    prefix inet;
  }
  import tailf-common {
    prefix tailf;
  }
  import tailf-ncs {
    prefix ncs;
  }

  description
    "Bla bla...";

  revision 2023-01-01 {
    description
      "Initial revision.";
  }

  typedef id-string {
    type string {
      pattern "[a-zA-Z0-9+_-]+";
    }
  }

  typedef sla-level {
    type enumeration {
      enum platinum;
      enum gold;
      enum silver;
      enum bronze;
    }
  }

  container arvpns {
    list arvpn {
      description "This is an RFS AR-VPN service";

      key client-name;
      leaf client-name {
        tailf:info "Unique service id";
        tailf:cli-allow-range;
        type id-string;
      }

      uses ncs:service-data;
      ncs:servicepoint arvpn-svc-servicepoint;

      leaf client-ip {
        type inet:ip-address;
      }

      leaf service-level-agreement {
        type sla-level;
        default bronze;
      }

      leaf datacenter-name {
        type leafref {
          path "/datacenters/datacenter/name";
        }
      }

      leaf vlan-id {
        config false;
        type int32 {
          range 1..4094;
        }
        description "The VLAN transport the client is using.";
      }
    }
  }

  augment /ncs:devices/ncs:device {
    leaf arvpn-service-capable {
      type empty;
    }
  }

  container datacenters {
    list datacenter {
      key name;
      leaf name {
        type string;
      }
      list firewall {
        key device-name;
        leaf device-name {
          type leafref {
            path "/ncs:devices/ncs:device/ncs:name";
          }
          must deref(.)/../arvpn-service-capable {
            tailf:dependency /ncs:devices/ncs:device/arvpn-service-capable;
            error-message 
              "Only AR VPN capable devices can be configured here.";
          }
        }
      }
    }
  }

  augment /ncs:devices/ncs:device {
    leaf arvpn-service-vpn {
      type empty;
    }
  }
}
